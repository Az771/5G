NR-MIB-RECEIVER DEFINITIONS AUTOMATIC TAGS ::=
BEGIN

BCCH-BCH-Message ::= SEQUENCE {
    message CHOICE {
        mib MIB
    }
}

MIB ::= SEQUENCE {
    systemFrameNumber         BIT STRING (SIZE (6)),
    subCarrierSpacingCommon   ENUMERATED {scs15or60, scs30or120},
    ssb-SubcarrierOffset      INTEGER (0..15),
    dmrs-TypeA-Position       ENUMERATED {pos2, pos3},
    pdcch-ConfigSIB1          PDCCH-ConfigSIB1,
    cellBarred                ENUMERATED {barred, notBarred},
    intraFreqReselection      ENUMERATED {allowed, notAllowed},
    spare                     BIT STRING (SIZE (1))
}

PDCCH-ConfigSIB1 ::= SEQUENCE {
    controlResourceSetZero    INTEGER (0..15),
    searchSpaceZero           INTEGER (0..15)
}

END
